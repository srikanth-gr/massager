# METADATA_START
# File Name: tennis_ball_holder.FCMacro
# Version: 8a29317
# Last Commit Date: 2026-06-03 15:20:43 +0200
# Last Comment: V7.17 design - Corrected side cup local axle rotation values and squared up pedestal depth alignment rules.
# METADATA_END

# FreeCAD V7.17 Synchronized Assembly Alignment Macro
import FreeCAD as App
import Part

# Initialize Document
doc = App.activeDocument()
if not doc:
    doc = App.newDocument("MassagerV717Master")

Base = App.Base

# Clean previous objects for a completely fresh build run
objects_to_clear = [
    "FinalAssembly", "YokeBody", "LeftCup", "RightCup", "CenterWheel",
    "RoundBase", "LeftArmBlock", "RightArmBlock", "LeftBlindPocket", "RightBlindPocket", 
    "YokeSolid", "YokeWithBores", "PedestalBlock", "PedestalPocket", "WheelPedestal",
    "LeftCupBlank", "LeftBallCut", "LeftCupBase", "RidgeLeft", "LeftCupTextured", "LeftAxle",
    "RightCupBlank", "RightBallCut", "RightCupBase", "RidgeRight", "RightCupTextured", "RightAxle",
    "ArmTrimmingTool", "CurvedArmsClean", "RawArmsCombined", "YokeFuse1", "YokeP1",
    "YokeWithPedestal", "PinHoleCutout", "FinalWheelHousing", "WheelBlank", "WheelBore",
    "FrontArmCutter", "YokeFrontCurved", "LeftCupEllipsoid", "RightCupEllipsoid",
    "TrimCylInner", "TrimBoxOuter"
]
for name in objects_to_clear:
    if doc.getObject(name):
        doc.removeObject(name)

# ==========================================
# 1. GEOMETRY PARAMETERS
# ==========================================
base_radius = 60.0       
base_thickness = 15.0
arm_thickness = 22.0
arm_cavity = 82.0        
arm_height = 68.0        
arm_depth = 40.0         

cup_diameter = 72.0
ball_radius = 33.5       
axle_radius = 4.0        
axle_length = 15.0       

wheel_radius = 6.0       
wheel_width = 16.0       
pedestal_height = 12.0   

half_cavity = arm_cavity / 2.0
rotation_axis_z = 45.0   

# ==========================================
# 2. BUILD ROUND BASE & FLUSH-TRIMMED SOLID ARMS
# ==========================================
round_base = doc.addObject("Part::Cylinder", "RoundBase")
round_base.Radius = base_radius
round_base.Height = base_thickness

left_arm = doc.addObject("Part::Box", "LeftArmBlock")
left_arm.Length = arm_thickness + 10.0
left_arm.Width = arm_depth
left_arm.Height = arm_height
left_arm.Placement = App.Placement(App.Vector(-half_cavity - arm_thickness, -arm_depth/2.0, base_thickness), App.Rotation(0, 0, 0))

right_arm = doc.addObject("Part::Box", "RightArmBlock")
right_arm.Length = arm_thickness + 10.0
right_arm.Width = arm_depth
right_arm.Height = arm_height
right_arm.Placement = App.Placement(App.Vector(half_cavity - 10.0, -arm_depth/2.0, base_thickness), App.Rotation(0, 0, 0))

raw_arms = doc.addObject("Part::Fuse", "RawArmsCombined")
raw_arms.Base = left_arm
raw_arms.Tool = right_arm

trim_cyl_inner = doc.addObject("Part::Cylinder", "TrimCylInner")
trim_cyl_inner.Radius = base_radius
trim_cyl_inner.Height = arm_height + 20.0

trim_box_outer = doc.addObject("Part::Box", "TrimBoxOuter")
trim_box_outer.Length = base_radius * 3.0
trim_box_outer.Width = base_radius * 3.0
trim_box_outer.Height = arm_height + 30.0
trim_box_outer.Placement = App.Placement(App.Vector(-base_radius * 1.5, -base_radius * 1.5, 0), App.Rotation(0,0,0))

trim_tool = doc.addObject("Part::Cut", "ArmTrimmingTool")
trim_tool.Base = trim_box_outer
trim_tool.Tool = trim_cyl_inner
trim_tool.Placement = App.Placement(App.Vector(0, 0, base_thickness), App.Rotation(0, 0, 0))

curved_arms_clean = doc.addObject("Part::Cut", "CurvedArmsClean")
curved_arms_clean.Base = raw_arms
curved_arms_clean.Tool = trim_tool

yoke_solid = doc.addObject("Part::Fuse", "YokeSolid")
yoke_solid.Base = round_base
yoke_solid.Tool = curved_arms_clean

# ==========================================
# 3. BUILD EXTRA SUPPORT: RAISED PEDESTAL HOUSING
# ==========================================
pedestal = doc.addObject("Part::Box", "PedestalBlock")
pedestal.Length = 24.0
pedestal.Width = 32.0    
pedestal.Height = pedestal_height
# Aligned center to center symmetrically with the depth of the support arms
pedestal.Placement = App.Placement(App.Vector(-12.0, -16.0, base_thickness), App.Rotation(0, 0, 0))

pedestal_pocket = doc.addObject("Part::Box", "PedestalPocket")
pedestal_pocket.Length = 14.0
pedestal_pocket.Width = 18.0    
pedestal_pocket.Height = pedestal_height + 2.0
pedestal_pocket.Placement = App.Placement(App.Vector(-7.0, -9.0, base_thickness + 2.0), App.Rotation(0, 0, 0))

raw_housing = doc.addObject("Part::Cut", "WheelPedestal")
raw_housing.Base = pedestal
raw_housing.Tool = pedestal_pocket

pin_hole = doc.addObject("Part::Cylinder", "PinHoleCutout")
pin_hole.Radius = 2.1    
pin_hole.Height = 40.0
pin_hole.Placement = App.Placement(App.Vector(0, -20.0, base_thickness + wheel_radius), App.Rotation(App.Vector(1,0,0), 90))

final_wheel_housing = doc.addObject("Part::Cut", "FinalWheelHousing")
final_wheel_housing.Base = raw_housing
final_wheel_housing.Tool = pin_hole

yoke_with_pedestal = doc.addObject("Part::Fuse", "YokeWithPedestal")
yoke_with_pedestal.Base = yoke_solid
yoke_with_pedestal.Tool = final_wheel_housing

# ==========================================
# 4. CONCEALED BLIND POCKETS FOR SIDE AXLES
# ==========================================
left_pocket = doc.addObject("Part::Cylinder", "LeftBlindPocket")
left_pocket.Radius = axle_radius + 0.25  
left_pocket.Height = 12.0
left_pocket.Placement = App.Placement(App.Vector(-half_cavity, 0, rotation_axis_z), App.Rotation(App.Vector(0,1,0), -90))

right_pocket = doc.addObject("Part::Cylinder", "RightBlindPocket")
right_pocket.Radius = axle_radius + 0.25
right_pocket.Height = 12.0
right_pocket.Placement = App.Placement(App.Vector(half_cavity, 0, rotation_axis_z), App.Rotation(App.Vector(0,1,0), 90))

yoke_p1 = doc.addObject("Part::Cut", "YokeP1")
yoke_p1.Base = yoke_with_pedestal
yoke_with_pedestal
yoke_p1.Tool = left_pocket

yoke_body = doc.addObject("Part::Cut", "YokeBody")
yoke_body.Base = yoke_p1
yoke_body.Tool = right_pocket

# ==========================================
# 5. STANDALONE LOWER SUPPORT WHEEL 
# ==========================================
wheel_blank = doc.addObject("Part::Cylinder", "WheelBlank")
wheel_blank.Radius = wheel_radius
wheel_blank.Height = wheel_width
wheel_blank.Placement = App.Placement(App.Vector(0, -wheel_width/2.0, base_thickness + wheel_radius), App.Rotation(App.Vector(1,0,0), 90))

wheel_bore = doc.addObject("Part::Cylinder", "WheelBore")
wheel_bore.Radius = 2.1  
wheel_bore.Height = 24.0
wheel_bore.Placement = App.Placement(App.Vector(0, -12.0, base_thickness + wheel_radius), App.Rotation(App.Vector(1,0,0), 90))

center_wheel = doc.addObject("Part::Cut", "CenterWheel")
center_wheel.Base = wheel_blank
center_wheel.Tool = wheel_bore

# ==========================================
# 6. BUILD LEFT ELLIPSOID CUP (AXLE DIRECTION FIXED)
# ==========================================
left_sph_geom = Part.makeSphere(cup_diameter / 2.0)
scale_mat_left = Base.Matrix()
scale_mat_left.scale(0.7, 1.0, 1.0) 
left_sph_geom.transformShape(scale_mat_left)

left_sph = doc.addObject("Part::Feature", "LeftCupEllipsoid")
left_sph.Shape = left_sph_geom
left_sph.Placement = App.Placement(App.Vector(-48.0, 0, rotation_axis_z), App.Rotation(App.Vector(0,1,0), 0))

left_ball_cut = doc.addObject("Part::Sphere", "LeftBallCut")
left_ball_cut.Radius = ball_radius
left_ball_cut.Placement = App.Placement(App.Vector(0, 0, rotation_axis_z), App.Rotation(0, 0, 0))

left_cup_base = doc.addObject("Part::Cut", "LeftCupBase")
left_cup_base.Base = left_sph
left_cup_base.Tool = left_ball_cut

left_axle = doc.addObject("Part::Cylinder", "LeftAxle")
left_axle.Radius = axle_radius
left_axle.Height = axle_length
# FIXED: Rotated 90 instead of -90 to project inward toward the arm housing pocket cleanly
left_axle.Placement = App.Placement(App.Vector(-48.0, 0, rotation_axis_z), App.Rotation(App.Vector(0,1,0), 90))

left_cup = doc.addObject("Part::Fuse", "LeftCup")
left_cup.Base = left_cup_base
left_cup.Tool = left_axle

# ==========================================
# 7. BUILD RIGHT ELLIPSOID CUP (AXLE DIRECTION FIXED)
# ==========================================
right_sph_geom = Part.makeSphere(cup_diameter / 2.0)
scale_mat_right = Base.Matrix()
scale_mat_right.scale(0.7, 1.0, 1.0)
right_sph_geom.transformShape(scale_mat_right)

right_sph = doc.addObject("Part::Feature", "RightCupEllipsoid")
right_sph.Shape = right_sph_geom
right_sph.Placement = App.Placement(App.Vector(48.0, 0, rotation_axis_z), App.Rotation(App.Vector(0,1,0), 0))

right_ball_cut = doc.addObject("Part::Sphere", "RightBallCut")
right_ball_cut.Radius = ball_radius
right_ball_cut.Placement = App.Placement(App.Vector(0, 0, rotation_axis_z), App.Rotation(0, 0, 0))

right_cup_base = doc.addObject("Part::Cut", "RightCupBase")
right_cup_base.Base = right_sph
right_cup_base.Tool = right_ball_cut

right_axle = doc.addObject("Part::Cylinder", "RightAxle")
right_axle.Radius = axle_radius
right_axle.Height = axle_length
# FIXED: Rotated -90 instead of 90 to face outward into the right side arm receiver
right_axle.Placement = App.Placement(App.Vector(48.0, 0, rotation_axis_z), App.Rotation(App.Vector(0,1,0), -90))

right_cup = doc.addObject("Part::Fuse", "RightCup")
right_cup.Base = right_cup_base
right_cup.Tool = right_axle

# ==========================================
# 8. ASSEMBLY COMPILATION
# ==========================================
assembly = doc.addObject("Part::Compound", "FinalAssembly")
assembly.Links = [yoke_body, center_wheel, left_cup, right_cup]

for obj in doc.Objects:
    if obj.Name != "FinalAssembly":
        obj.Visibility = False

assembly.Visibility = True
doc.recompute()
App.Console.PrintMessage("FreeCAD V7.17 Perfect Spatial Fit Alignment Generated!\n")
